module danos-types {
  yang-version 1.1;
  namespace "urn:danos:types";
  prefix dt;

  description
    "DANOS-Open common type definitions.
     Copyright (c) 2026 DANOS-Open Project. Apache-2.0.";

  revision 2026-09-05 {
    description "Initial version for v0.1.";
  }

  typedef vrf-id {
    type uint32 { range "0..4095"; }
    description "VRF identifier. 0 = default VRF.";
  }

  typedef ifindex {
    type uint32 { range "1..4294967295"; }
    description "Interface index.";
  }

  typedef vlan-id {
    type uint32 { range "1..4094"; }
    description "IEEE 802.1Q VLAN identifier.";
  }

  typedef mpls-label {
    type uint32 { range "0..1048575"; }
    description "MPLS label (20 bits).";
  }

  typedef vni {
    type uint32 { range "0..16777215"; }
    description "VXLAN VNI (24 bits).";
  }

  typedef route-protocol {
    type enumeration {
      enum kernel     { value 1; }
      enum static     { value 2; }
      enum bgp        { value 3; }
      enum ospf       { value 4; }
      enum isis       { value 5; }
      enum connected  { value 6; }
    }
  }

  typedef admin-distance {
    type uint32 { range "0..255"; }
  }

  typedef ip-prefix {
    type string {
      pattern
        '(([0-9]|[1-9][0-9]|1[0-9][0-9]|2[0-4][0-9]|25[0-5])\.){3}'
      + '([0-9]|[1-9][0-9]|1[0-9][0-9]|2[0-4][0-9]|25[0-5])'
      + '/([0-9]|[12][0-9]|3[0-2])';
    }
  }
}
