module danos-nhgroup {
  yang-version 1.1;
  namespace "urn:danos:nhgroup";
  prefix dnhg;

  description
    "DANOS-Open next-hop group (ECMP / weighted ECMP / backup) model.
     Copyright (c) 2026 DANOS-Open Project. Apache-2.0.";

  revision 2026-09-06 {
    description "v0.2: initial next-hop group model (up to 64 NHs).";
  }

  container nhgroups {
    list nhgroup {
      key "id";
      leaf id { type uint64; }
      leaf-list nh-ids { type uint64; }
      leaf flags { type uint32; default 0; }
    }
  }
}
