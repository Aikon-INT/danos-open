module danos-acl {
  yang-version 1.1;
  namespace "urn:danos:acl";
  prefix dacl;

  import danos-types { prefix dt; }

  description
    "DANOS-Open ACL model.
     Copyright (c) 2026 DANOS-Open Project. Apache-2.0.";

  revision 2026-09-06 {
    description "v0.2: add action params (redirect/police/set-dscp), fields-mask.";
  }

  revision 2026-09-05 {
    description "Initial version for v0.1.";
  }

  typedef acl-action {
    type enumeration {
      enum permit   { value 1; }
      enum deny     { value 2; }
      enum mirror   { value 3; }
      enum redirect { value 4; }
      enum police   { value 5; }
      enum set-dscp { value 6; }
    }
  }

  typedef acl-field {
    type enumeration {
      enum ether-type  { value 0; }
      enum src-mac     { value 1; }
      enum dst-mac     { value 2; }
      enum vlan-id     { value 3; }
      enum src-ip      { value 4; }
      enum dst-ip      { value 5; }
      enum l4-proto    { value 6; }
      enum l4-src-port { value 7; }
      enum l4-dst-port { value 8; }
      enum dscp        { value 9; }
    }
  }

  container acl {
    list table {
      key "table-id";
      leaf table-id { type uint64; }
      leaf name { type string; }
      leaf bind-ifindex { type dt:ifindex; }
      leaf ingress { type boolean; default true; }

      list rule {
        key "rule-id";
        leaf rule-id { type uint64; }
        leaf priority { type uint32; }
        leaf action { type acl-action; }

        /* Action parameters (v0.2) */
        leaf redirect-ifindex { type dt:ifindex; }
        leaf police-rate-kbps { type uint32; }
        leaf set-dscp-value   { type uint8 { range "0..63"; } }

        container match {
          /* Bitmask of active match fields (v0.2) */
          leaf-list fields { type acl-field; }

          leaf ether-type { type uint16; }
          leaf src-mac { type string; }
          leaf dst-mac { type string; }
          leaf vlan-id { type dt:vlan-id; }
          leaf src-ip { type dt:ip-prefix; }
          leaf dst-ip { type dt:ip-prefix; }
          leaf l4-proto { type uint8; }
          leaf l4-src-port-start { type uint16; }
          leaf l4-src-port-end   { type uint16; }
          leaf l4-dst-port-start { type uint16; }
          leaf l4-dst-port-end   { type uint16; }
          leaf dscp { type uint8; }
        }
      }
    }
  }
}
